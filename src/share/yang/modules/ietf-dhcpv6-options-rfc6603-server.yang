module ietf-dhcpv6-options-rfc6603 {
  yang-version 1.1;
  namespace "urn:ietf:params:xml:ns:yang:ietf-dhcpv6-options-rfc6603-server";
  prefix rfc6603-srv;

  import ietf-inet-types {
    prefix inet;
  }

  import ietf-dhcpv6-server {
    prefix dhcpv6-server;
  }

  organization
    "DHC WG";
  contact
    "ian.farrer@telekom.de";
  description
    "This YANG module contains DHCPv6 options defined
     in RFC6603 that can be used by DHCPv6 servers.";

  revision 2020-02-21 {
    description
      "Initial version.";
    reference
      "I-D: draft-ietf-dhc-dhcpv6-yang";
  }

  grouping pd-exclude-option-group {
    container pd-exclude {
      if-feature "dhcpv6-server:prefix-delegation";
      description
        "OPTION_PD_EXCLUDE (67) PD Exclude Option.";
      reference
        "RFC6603: Prefix Exclude Option for DHCPv6-based
         Prefix Delegation";
      leaf ipv6-subnet {
        type inet:ipv6-prefix;
        description
          "The IPv6 Subnet ID and prefix-len that the
           delegating router includes in the OPTION_PD_EXCLUDE
           option that is excluded from the delegated prefix set.";
      }
    }
  }

  augment "/dhcpv6-server:dhcpv6-server/dhcpv6-server:network-ranges/dhcpv6-server:network-range/dhcpv6-server:prefix-pools/dhcpv6-server:prefix-pool" {
    uses pd-exclude-option-group;
  }
}
