module ietf-dhcpv6-server-for-distributed {
  yang-version 1.1;
  namespace "urn:ietf:params:xml:ns:yang:ietf-dhcpv6-server-for-distributed";
  prefix dhcpv6-server;

  import ietf-inet-types {
    prefix inet;
  }

  import ietf-yang-types {
    prefix yang;
  }

  import ietf-dhcpv6-common {
    prefix dhcpv6-common;
  }

  import kea-dhcp6-server {
    prefix kea-dhcp6-server;
  }

  import kea-dhcp-types {
    prefix kea-dhcp-types;
  }

  organization
    "DHC WG";
  contact
    "cuiyong@tsinghua.edu.cn
     lh.sunlinh@gmail.com
     ian.farrer@telekom.de
     sladjana.zechlin@telekom.de
     hezihao9512@gmail.com
     godfryd@isc.org";
  description
    "This YANG module defines components for the
     configuration and management of DHCPv6 servers.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 8513; see
     the RFC itself for full legal notices.";

  revision 2020-05-26 {
    description
      "Version update for draft -11 publication and
       to align revisions across the different modules.";
    reference
      "I-D: draft-ietf-dhc-dhcpv6-yang-11";
  }
  revision 2019-12-02 {
    description
      "Major reworking of the module.";
    reference
      "I-D: draft-ietf-dhc-dhcpv6-yang-10";
  }
  revision 2018-09-04 {
    description
      "";
    reference
      "I-D: draft-ietf-dhc-dhcpv6-yang";
  }
  revision 2018-03-04 {
    description
      "Resolved most issues on the DHC official
       github";
    reference
      "I-D: draft-ietf-dhc-dhcpv6-yang";
  }
  revision 2017-12-22 {
    description
      "Resolve most issues on Ian's github.";
    reference
      "I-D: draft-ietf-dhc-dhcpv6-yang";
  }
  revision 2017-11-24 {
    description
      "First version of the separated server specific
       YANG model.";
    reference
      "I-D: draft-ietf-dhc-dhcpv6-yang";
  }

  feature prefix-delegation {
    description
      "Denotes that the server implements DHCPv6 prefix
       delegation.";
  }

  identity server {
    base dhcpv6-common:dhcpv6-node;
    description
      "DHCPv6 server identity.";
  }

  grouping resource-config {
    description
      "Nodes that are reused at multiple levels in the
       DHCPv6 server's addressing hierarchy.";
    leaf-list option-set-id {
      type leafref {
        path "/dhcpv6-server:dhcpv6-server/dhcpv6-server:option-sets/dhcpv6-server:option-set/dhcpv6-server:option-set-id";
      }
      description
        "The ID field of relevant set of DHCPv6 options
         (option-set) to be provisioned to clients of this
         network-range.";
    }

    leaf valid-lifetime {
      type dhcpv6-common:timer-seconds32;
      description
        "Valid lifetime for the Identity Association
         (IA).";
    }

    leaf renew-time {
      type dhcpv6-common:timer-seconds32;
      description
        "Renew (T1) time.";
    }

    leaf rebind-time {
      type dhcpv6-common:timer-seconds32;
      description
        "Rebind (T2) time.";
    }

    leaf preferred-lifetime {
      type dhcpv6-common:timer-seconds32;
      description
        "Preferred lifetime for the Identity Association
         (IA).";
    }

    leaf rapid-commit {
      type boolean;
      description
        "A value of 1 specifies that the pool supports
         client-server exchanges involving two messages.";
    }
  }

  grouping lease-information {
    description
      "Binding information for each client that has
       been allocated an IPv6 address or prefix.";
    leaf client-duid {
      type binary;
      description
        "Client DUID.";
    }

    leaf iaid {
      type uint32;
      mandatory true;
      description
        "Client's IAID";
    }

    leaf allocation-time {
      type yang:date-and-time;
      description
        "Time and date that the lease was made.";
    }

    leaf last-renew-rebind {
      type yang:date-and-time;
      description
        "Time of the last successful renew or
         rebind.";
    }

    leaf preferred-lifetime {
      type dhcpv6-common:timer-seconds32;
      description
        "The preferred lifetime expressed in
         seconds.";
    }

    leaf valid-lifetime {
      type dhcpv6-common:timer-seconds32;
      description
        "The valid lifetime for the leased prefix
         expressed in seconds.";
    }

    leaf lease-t1 {
      type dhcpv6-common:timer-seconds32;
      description
        "The time interval after which the client
         should contact the server from which the addresses
         in the IA_NA were obtained to extend the lifetimes
         of the addresses assigned to the IA_PD.";
    }

    leaf lease-t2 {
      type dhcpv6-common:timer-seconds32;
      description
        "The time interval after which the client
         should contact any available server to extend
         the lifetimes of the addresses assigned to the
         IA_PD.";
    }
  }

  grouping message-stats {
    description
      "Counters for DHCPv6 messages.";
    leaf solicit-count {
      type uint32;
      config false;
      description
        "Number of Solicit (1) messages received.";
    }

    leaf advertise-count {
      type uint32;
      config false;
      description
        "Number of Advertise (2) messages sent.";
    }

    leaf request-count {
      type uint32;
      config false;
      description
        "Number of Request (3) messages received.";
    }

    leaf confirm-count {
      type uint32;
      config false;
      description
        "Number of Confirm (4) messages received.";
    }

    leaf renew-count {
      type uint32;
      config false;
      description
        "Number of Renew (5) messages received.";
    }

    leaf rebind-count {
      type uint32;
      config false;
      description
        "Number of Rebind (6) messages received.";
    }

    leaf reply-count {
      type uint32;
      config false;
      description
        "Number of Reply (7) messages sent.";
    }

    leaf release-count {
      type uint32;
      description
        "Number of Release (8) messages received.";
    }

    leaf decline-count {
      type uint32;
      config false;
      description
        "Number of Decline (9) messages received.";
    }

    leaf reconfigure-count {
      type uint32;
      config false;
      description
        "Number of Reconfigure (10) messages sent.";
    }

    leaf information-request-count {
      type uint32;
      config false;
      description
        "Number of Information-request (11) messages
         received.";
    }
  }

  grouping dhcpv6-server {
    container server-duid {
      description
        "DUID of the server.";
      uses dhcpv6-common:duid;
    }

    container vendor-config {
      description
        "This container provides a location for
         augmenting vendor or implementation specific
         configuration nodes.";
    }

    container option-sets {
      description
        "A server may allow different option sets
         to be configured for clients matching specific parameters
         such as topological location or client type. The
         'option-set' list is a set of options and their
         contents that will be returned to clients.";
      list option-set {
        key "option-set-id";
        description
          "YANG definitions for DHCPv6 options are
           contained in separate YANG modules and augmented to this
           container as required.";
        leaf option-set-id {
          type uint32;
          description
            "Option set identifier.";
        }

        leaf description {
          type string;
          description
            "An optional field for storing additional
             information relevant to the option set.";
        }
      }
    }

    container class-selector {
      description
        "DHCPv6 servers use a 'class-selector' function
         in order to identify and classify incoming client messages
         so that they can be given the correct configuration.
         The mechanisms used for implementing this function vary
         greatly between different implementations such that they
         are not possible to include in this module. This container
         provides a location for server implementors to augment
         their own class-selector YANG.";
    }

    container network-ranges {
      description
        "This model is based on an address and parameter
         allocation hierarchy.  The top level is 'global' - which
         is defined as the container for all network-ranges. Under
         this are the individual network-ranges.";
      uses resource-config;

      list network-range {
        key "network-range-id";
        description
          "Network-ranges are identified by the
           'network-range-id' key.";
        leaf network-range-id {
          type uint32;
          mandatory true;
          description
            "Equivalent to subnet ID.";
        }

        leaf network-description {
          type string;
          mandatory true;
          description
            "Description for the network range.";
        }

        leaf network-prefix {
          type inet:ipv6-prefix;
          mandatory true;
          description
            "Network prefix.";
        }

        uses resource-config;

        container address-pools {
          description
            "Configuration for the DHCPv6 server's
             address pools.";
          list address-pool {
            key "pool-id";
            description
              "List of address pools for allocation to
               clients, distinguished by 'pool-id'.";
            leaf pool-id {
              type uint32;
              mandatory true;
              description
                "Unique identifier for the pool.";
            }

            leaf pool-prefix {
              type inet:ipv6-prefix;
              mandatory true;
              description
                "IPv6 prefix for the pool.";
            }

            leaf start-address {
              type inet:ipv6-address-no-zone;
              mandatory true;
              description
                "Start IPv6 address for the pool.";
            }

            leaf end-address {
              type inet:ipv6-address-no-zone;
              mandatory true;
              description
                "End IPv6 address for the pool.";
            }

            leaf max-address-count {
              type dhcpv6-common:threshold;
              mandatory true;
              description
                "Maximum number of addresses that can
                 be simultaneously allocated from this pool.";
            }

            uses resource-config;

            container host-reservations {
              description
                "Configuration for host reservations from
                 the address pool.";
              list host-reservation {
                key "reserved-addr";
                leaf client-duid {
                  type binary;
                  description
                    "Client DUID for the reservation.";
                }

                leaf reserved-addr {
                  type inet:ipv6-address;
                  description
                    "Reserved IPv6 address.";
                }

                uses resource-config;
              }
            }

            container active-leases {
              config false;
              description
                "Holds state related to active client
                 leases.";
              leaf total-count {
                type uint64;
                mandatory true;
                description
                  "The total number of addresses in the
                   pool.";
              }

              leaf allocated-count {
                type uint64;
                mandatory true;
                description
                  "The number of addresses or prefixes
                   in the pool that are currently allocated.";
              }

              list active-lease {
                key "leased-address";
                leaf leased-address {
                  type inet:ipv6-address;
                }

                uses lease-information;
              }
            }
          }
        }

        container prefix-pools {
          if-feature "prefix-delegation";
          description
            "Configuration for the DHCPv6 server's
             prefix pools.";
          list prefix-pool {
            key "pool-id";
            description
              "List of prefix pools for allocation to
               clients, distinguished by 'pool-id'.";
            leaf pool-id {
              type uint32;
              mandatory true;
              description
                "Unique identifier for the pool.";
            }

            leaf pool-prefix {
              type inet:ipv6-prefix;
              mandatory true;
              description
                "IPv6 prefix for the pool.";
            }

            leaf client-prefix-length {
              type uint8;
              mandatory true;
              description
                "Length of the prefixes that will be
                 delegated to clients.";
            }

            leaf max-pd-space-utilization {
              type dhcpv6-common:threshold;
              mandatory true;
              description
                "Maximum percentage utilization of the
                 prefix pool in this pool.";
            }

            uses resource-config;

            container host-reservations {
              description
                "Configuration for host reservations
                 from the prefix pool.";
              list prefix-reservation {
                key "reserved-prefix";
                description
                  "reserved prefix reservation";
                leaf client-duid {
                  type binary;
                  description
                    "Client DUID for the reservation.";
                }

                leaf reserved-prefix {
                  type inet:ipv6-prefix;
                  description
                    "Reserved IPv6 prefix";
                }

                leaf reserved-prefix-len {
                  type uint8;
                  description
                    "Reserved IPv6 prefix length.";
                }
              }

              uses resource-config;
            }

            container active-leases {
              config false;
              description
                "Holds state related to for active client
                 prefix leases.";
              leaf total-count {
                type uint64;
                mandatory true;
                description
                  "The total number of prefixes in
                   the pool.";
              }

              leaf allocated-count {
                type uint64;
                mandatory true;
                description
                  "The number of prefixes in the pool
                   that are currently allocated.";
              }

              list active-lease {
                key "leased-prefix";
                leaf leased-prefix {
                  type inet:ipv6-prefix;
                }

                uses lease-information;
              }
            }
          }
        }
      }

      uses message-stats;
    }
  }

  leaf dhcpv6-node-type {
    type identityref {
      base dhcpv6-common:dhcpv6-node;
    }
    description
      "Type for a DHCPv6 server.";
  }

  container dhcpv6-server {
    uses dhcpv6-server;
  }

  notification address-pool-utilization-threshold-exceeded {
    description
      "Notification sent when the address pool
       utilization exceeds the configured threshold.";
    leaf pool-id {
      type leafref {
        path "/dhcpv6-server/network-ranges/network-range/address-pools/address-pool/pool-id";
      }
    }

    leaf total-address-count {
      type uint64;
      mandatory true;
      description
        "Count of the total addresses in the pool.";
    }

    leaf max-address-count {
      type uint64;
      mandatory true;
      description
        "Maximum count of addresses that can be allocated
         in the pool. This value may be less than count of total
         addresses.";
    }

    leaf allocated-address-count {
      type uint64;
      mandatory true;
      description
        "Count of allocated addresses in the pool.";
    }
  }

  notification prefix-pool-utilization-threshold-exceeded {
    if-feature "prefix-delegation";
    description
      "Notification sent when the prefix pool
       utilization exceeds the configured threshold.";
    leaf pool-id {
      type leafref {
        path "/dhcpv6-server/network-ranges/network-range/prefix-pools/prefix-pool/pool-id";
      }
      mandatory true;
    }

    leaf max-pd-space-utilization {
      type leafref {
        path "/dhcpv6-server/network-ranges/network-range/prefix-pools/prefix-pool/max-pd-space-utilization";
      }
      mandatory true;
      description
        "PD space utilization threshold.";
    }

    leaf pd-space-utilization {
      type uint64;
      description
        "Current PD space utilization";
    }
  }

  notification invalid-client-detected {
    description
      "Notification sent when the server detects an
       invalid client.";
    leaf duid {
      type binary;
      description
        "Client DUID.";
    }

    leaf description {
      type string;
      description
        "Description of the event (e.g. and error code or
         log message).";
    }
  }

  notification decline-received {
    description
      "Notification sent when the server has received a
       Decline (9) message from a client.";
    leaf duid {
      type binary;
      description
        "Client DUID.";
    }

    list declined-resources {
      description
        "List of declined addresses and/or prefixes.";
      choice resource-type {
        case declined-address {
          leaf address {
            type inet:ipv6-address;
          }
        }

        case declined-prefix {
          leaf prefix {
            type inet:ipv6-prefix;
          }
        }
      }
    }
  }

  notification non-success-code-sent {
    description
      "Notification sent when the server responded
       to a client with non-success status code.";
    leaf status-code {
      type uint16;
      mandatory true;
      description
        "Status code returned to the client.";
    }

    leaf duid {
      type binary;
      description
        "Client DUID.";
    }
  }
}
