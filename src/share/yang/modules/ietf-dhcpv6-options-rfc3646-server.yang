module ietf-dhcpv6-options-rfc3646 {
  yang-version 1.1;
  namespace "urn:ietf:params:xml:ns:yang:ietf-dhcpv6-options-rfc3646-server";
  prefix rfc3646-srv;

  import ietf-inet-types {
    prefix inet;
  }

  import ietf-dhcpv6-server {
    prefix dhcpv6-server;
  }

  organization
    "DHC WG";
  contact
    "ian.farrer@telekom.de";
  description
    "This YANG module contains DHCPv6 options defined
     in RFC3319 that can be used by DHCPv6 servers.";

  revision 2020-02-21 {
    description
      "Initial version.";
    reference
      "I-D: draft-ietf-dhc-dhcpv6-yang";
  }

  grouping dns-servers-option-group {
    container dns-servers-option {
      description
        "OPTION_DNS_SERVERS (23) DNS recursive Name Server option";
      reference
        "RFC3646: DNS Configuration options for Dynamic Host
         Configuration Protocol for IPv6 (DHCPv6)";
      list dns-server {
        key "dns-serv-id";
        description
          "List of DNS server addresses.";
        leaf dns-serv-id {
          type uint8;
          description
            "DNS server list entry ID.";
        }

        leaf dns-serv-addr {
          type inet:ipv6-address;
          description
            "DNS server address.";
        }
      }
    }
  }

  grouping domain-searchlist-option-group {
    container domain-searchlist-option {
      description
        "OPTION_DOMAIN_LIST (24) Domain Search List Option";
      reference
        "RFC3646: DNS Configuration options for Dynamic
         Host Configuration Protocol for IPv6 (DHCPv6)";
      list domain-searchlist {
        key "domain-searchlist-id";
        description
          "List of DNS search domains.";
        leaf domain-searchlist-id {
          type uint8;
          description
            "Domain seachlist entry ID.";
        }

        leaf domain-search-list-entry {
          type string;
          description
            "Domain search list entry.";
        }
      }
    }
  }

  augment "/dhcpv6-server:dhcpv6-server/dhcpv6-server:option-sets/dhcpv6-server:option-set" {
    uses dns-servers-option-group;

    uses domain-searchlist-option-group;
  }
}
