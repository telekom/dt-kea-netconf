module dt-kea-dhcp4-distributed {
  yang-version 1.1;
  namespace "urn:ietf:params:xml:ns:yang:dt-kea-dhcp4-distributed";
  prefix dt-kea-dhcp4-distributed;

  import kea-dhcp4-server {
    prefix kea-dhcp4-server;
  }

  import kea-dhcp-types {
    prefix kea-dhcp-types;
  }

  import kea-types {
    prefix kea-types;
  }

  organization
    "Deutsche Telekom AG.";
  contact
    "andrei.pavel@qualitance.com";
  description
    "Can be used to configure and manage multiple Kea DHCPv4 servers via the master-shards paradigm.";

  revision 2020-01-30;

  container config {
    description
      "Contains DHCPv4 master configuration.";
    leaf skip-validation {
      type boolean;
      description
        "used internally to differentiate external client commands from self issued commands";
    }

    list masters {
      key "name";
      leaf name {
        type string;
        mandatory true;
        description
          "master's name : keyspace";
      }

      container admin-credentials {
        description
          "master.ini";
        uses kea-dhcp-types:database;
      }

      list shards {
        key "name";
        leaf name {
          type string;
          mandatory true;
          description
            "shard's name";
        }

        container admin-credentials {
          description
            "credentials.json";
          uses kea-dhcp-types:database;
        }

        container config-database {
          description
            "config-database in servers.json";
          uses kea-dhcp-types:database;
        }

        list master-config {
          key "instance-id";
          description
            "master-config in servers.json";
          uses kea-dhcp-types:instance-id;

          container server-config {
            container Dhcp4 {
              uses kea-dhcp4-server:Dhcp4;
            }
          }
        }

        container shard-config {
          description
            "config.json";
          container Dhcp4 {
            uses kea-dhcp4-server:Dhcp4;
          }
        }
      }
    }
  }
}
